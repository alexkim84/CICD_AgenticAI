# crs_req_func_ears
Draft EARS rewrite of crs_req_func_spec.slreqx. Review and approve before baselining.

## #1: Driver Switch Request Handling (Functional)
The cruise control controller shall convert driver switch inputs into a driver request command.
- Rationale: EARS rewrite of source requirement #1; technical intent requires engineering review before approval.
- Keywords: draft, EARS, source-linked

### #2: Switch precedence (Functional)
When multiple driver switches are active simultaneously, the cruise control controller shall apply the precedence Cancel, Cruise, Set, Resume, Increment, then Decrement.
- Rationale: EARS rewrite of source requirement #2; technical intent requires engineering review before approval.
- Keywords: draft, EARS, source-linked

### #3: Avoid repeating commands (Functional)
While Cancel, Cruise, Set, or Resume remains continuously active after its first accepted request, the cruise control controller shall output reqMode.NoRequest.
- Rationale: EARS rewrite of source requirement #3; technical intent requires engineering review before approval.
- Keywords: draft, EARS, source-linked

### #4: Long Switch recognition (Functional)
When the Increment or Decrement switch remains pressed for at least 500 ms, the cruise control controller shall classify the request as reqMode.Inc_Long or reqMode.Dec_Long, respectively.
- Rationale: EARS rewrite of source requirement #4; technical intent requires engineering review before approval.
- Keywords: draft, EARS, source-linked

#### #5: Waiting state for Long Increment switch detection (Functional)
While the Increment switch remains pressed for less than 500 ms, the cruise control controller shall output reqMode.Inc_Middle until long-press classification is reached.
- Rationale: EARS rewrite of source requirement #5; technical intent requires engineering review before approval.
- Keywords: draft, EARS, source-linked

#### #6: Waiting state for Long Decrement switch detection (Functional)
While the Decrement switch remains pressed for less than 500 ms, the cruise control controller shall output reqMode.Dec_Middle until long-press classification is reached.
- Rationale: EARS rewrite of source requirement #6; technical intent requires engineering review before approval.
- Keywords: draft, EARS, source-linked

### #7: Cancel Switch Detection (Functional)
When the Cancel switch is pressed, the cruise control controller shall set reqDrv to reqMode.Cancel.
- Rationale: EARS rewrite of source requirement #7; technical intent requires engineering review before approval.
- Keywords: draft, EARS, source-linked

### #8: Set Switch Detection (Functional)
When the Set switch is pressed, the cruise control controller shall set reqDrv to reqMode.Set.
- Rationale: EARS rewrite of source requirement #8; technical intent requires engineering review before approval.
- Keywords: draft, EARS, source-linked

### #9: Enable Switch Detection (Functional)
When the Enable switch is pressed, the cruise control controller shall set reqDrv to reqMode.Cruise.
- Rationale: EARS rewrite of source requirement #9; technical intent requires engineering review before approval.
- Keywords: draft, EARS, source-linked

### #10: Resume Switch Detection (Functional)
When the Resume switch is pressed, the cruise control controller shall set reqDrv to reqMode.Resume.
- Rationale: EARS rewrite of source requirement #10; technical intent requires engineering review before approval.
- Keywords: draft, EARS, source-linked

### #11: Increment Switch Detection (Functional)
When the Increment switch is pressed, the cruise control controller shall set reqDrv to reqMode.Inc_Short, reqMode.Inc_Middle, or reqMode.Inc_Long according to the press duration.
- Rationale: EARS rewrite of source requirement #11; technical intent requires engineering review before approval.
- Keywords: draft, EARS, source-linked

#### #12: Increment Short Switch Detection (Functional)
When the Increment switch is released before the 500 ms long-press threshold, the cruise control controller shall set reqDrv to reqMode.Inc_Short.
- Rationale: EARS rewrite of source requirement #12; technical intent requires engineering review before approval.
- Keywords: draft, EARS, source-linked

#### #13: Increment Long Switch Detection (Functional)
When the Increment switch remains pressed for at least 500 ms, the cruise control controller shall set reqDrv to reqMode.Inc_Long.
- Rationale: EARS rewrite of source requirement #13; technical intent requires engineering review before approval.
- Keywords: draft, EARS, source-linked

#### #14: Intermediate state (Functional)
While the Increment switch remains pressed and the 500 ms long-press threshold has not been reached, the cruise control controller shall set reqDrv to reqMode.Inc_Middle.
- Rationale: EARS rewrite of source requirement #14; technical intent requires engineering review before approval.
- Keywords: draft, EARS, source-linked

### #15: Decrement Switch Detection (Functional)
When the Decrement switch is pressed, the cruise control controller shall set reqDrv to reqMode.Dec_Short, reqMode.Dec_Middle, or reqMode.Dec_Long according to the press duration.
- Rationale: EARS rewrite of source requirement #15; technical intent requires engineering review before approval.
- Keywords: draft, EARS, source-linked

#### #16: Decrement Short Switch Detection (Functional)
When the Decrement switch is released before the 500 ms long-press threshold, the cruise control controller shall set reqDrv to reqMode.Dec_Short.
- Rationale: EARS rewrite of source requirement #16; technical intent requires engineering review before approval.
- Keywords: draft, EARS, source-linked

#### #17: Decrement Long Switch Detection (Functional)
When the Decrement switch remains pressed for at least 500 ms, the cruise control controller shall set reqDrv to reqMode.Dec_Long.
- Rationale: EARS rewrite of source requirement #17; technical intent requires engineering review before approval.
- Keywords: draft, EARS, source-linked

#### #18: Intermediate state (Functional)
While the Decrement switch remains pressed and the 500 ms long-press threshold has not been reached, the cruise control controller shall set reqDrv to reqMode.Dec_Middle.
- Rationale: EARS rewrite of source requirement #18; technical intent requires engineering review before approval.
- Keywords: draft, EARS, source-linked

## #19: Cruise Control Mode (Functional)
The cruise control controller shall determine its operating mode from the driver request and environmental conditions and shall provide the instrument-panel status.
- Rationale: EARS rewrite of source requirement #19; technical intent requires engineering review before approval.
- Keywords: draft, EARS, source-linked

### #20: Disable Cruise Control system (Functional)
If any cruise-control disable condition is true, then the cruise control controller shall enter the Disabled mode.
- Rationale: EARS rewrite of source requirement #20; technical intent requires engineering review before approval.
- Keywords: draft, EARS, source-linked

#### #21: Key position is not ON (Functional)
If the key position is not ON, then the cruise control controller shall enter the Disabled mode.
- Rationale: EARS rewrite of source requirement #21; technical intent requires engineering review before approval.
- Keywords: draft, EARS, source-linked

#### #22: Gear position is not Drive (Functional)
If the gear position is not Drive, then the cruise control controller shall enter the Disabled mode.
- Rationale: EARS rewrite of source requirement #22; technical intent requires engineering review before approval.
- Keywords: draft, EARS, source-linked

#### #23: Brake pressure is higher than brake_threshold (Functional)
If brake pressure is greater than brake_threshold (5), then the cruise control controller shall enter the Disabled mode.
- Rationale: EARS rewrite of source requirement #23; technical intent requires engineering review before approval.
- Keywords: draft, EARS, source-linked

### #24: Operation mode determination (Functional)
When a driver request or environmental condition is evaluated, the cruise control controller shall determine the current operating mode from that input and the previous operating mode.
- Rationale: EARS rewrite of source requirement #24; technical intent requires engineering review before approval.
- Keywords: draft, EARS, source-linked

#### #25: Precedence of mode determination (Functional)
When multiple mode-transition conditions are true simultaneously, the cruise control controller shall apply the precedence Disable, Enable, Resume, Activate, Increment, then Decrement.
- Rationale: EARS rewrite of source requirement #25; technical intent requires engineering review before approval.
- Keywords: draft, EARS, source-linked

#### #26: Disable conditions (Functional)
If a disable condition is true, then the cruise control controller shall request the Disabled mode.
- Rationale: EARS rewrite of source requirement #26; technical intent requires engineering review before approval.
- Keywords: draft, EARS, source-linked

#### #27: Enable conditions (Functional)
When all enable conditions are satisfied, the cruise control controller shall request the Enabled mode.
- Rationale: EARS rewrite of source requirement #27; technical intent requires engineering review before approval.
- Keywords: draft, EARS, source-linked

#### #28: Resume conditions (Functional)
When all resume conditions are satisfied, the cruise control controller shall request the Resume mode.
- Rationale: EARS rewrite of source requirement #28; technical intent requires engineering review before approval.
- Keywords: draft, EARS, source-linked

#### #29: Activate conditions (Functional)
When all activation conditions are satisfied, the cruise control controller shall request the Activated mode.
- Rationale: EARS rewrite of source requirement #29; technical intent requires engineering review before approval.
- Keywords: draft, EARS, source-linked

#### #30: Repeat previous operation mode (Functional)
When no mode-transition condition is true, the cruise control controller shall retain the previous operating mode.
- Rationale: EARS rewrite of source requirement #30; technical intent requires engineering review before approval.
- Keywords: draft, EARS, source-linked

#### #31: Increment mode (Functional)
While the cruise control controller is in increment mode, the controller shall increase the target speed.
- Rationale: EARS rewrite of source requirement #31; technical intent requires engineering review before approval.
- Keywords: draft, EARS, source-linked

#### #32: Increment and hold mode (Functional)
While the cruise control controller is in increment-and-hold mode, the controller shall increase and retain the target speed.
- Rationale: EARS rewrite of source requirement #32; technical intent requires engineering review before approval.
- Keywords: draft, EARS, source-linked

#### #33: Decrement mode (Functional)
While the cruise control controller is in decrement mode, the controller shall decrease the target speed.
- Rationale: EARS rewrite of source requirement #33; technical intent requires engineering review before approval.
- Keywords: draft, EARS, source-linked

#### #34: Decrement and hold mode (Functional)
While the cruise control controller is in decrement-and-hold mode, the controller shall decrease and retain the target speed.
- Rationale: EARS rewrite of source requirement #34; technical intent requires engineering review before approval.
- Keywords: draft, EARS, source-linked

#### #35: Out of speed range detection (Functional)
If vehicle speed is less than tsp_min (40) or greater than tsp_max (100), then the cruise control controller shall assert the out-of-range flag.
- Rationale: EARS rewrite of source requirement #35; technical intent requires engineering review before approval.
- Keywords: draft, EARS, source-linked

#### #36: Disabling override (Functional)
If any disable condition is true, then the cruise control controller shall select Disabled mode regardless of lower-priority mode requests.
- Rationale: EARS rewrite of source requirement #36; technical intent requires engineering review before approval.
- Keywords: draft, EARS, source-linked

## #37: Calculate Target Speed and Throttle Value (Functional)
The cruise control controller shall calculate target speed and throttle command from operating mode, vehicle speed, and driver throttle input.
- Rationale: EARS rewrite of source requirement #37; technical intent requires engineering review before approval.
- Keywords: draft, EARS, source-linked

### #38: Disabled case (Functional)
While the operating mode is Disabled, the cruise control controller shall set the throttle command to the driver throttle input and the target speed to tsp_min (40).
- Rationale: EARS rewrite of source requirement #38; technical intent requires engineering review before approval.
- Keywords: draft, EARS, source-linked

### #39: Enabled case (Functional)
While the operating mode is Enabled, the cruise control controller shall set target speed to current vehicle speed and throttle command to the driver throttle input.
- Rationale: EARS rewrite of source requirement #39; technical intent requires engineering review before approval.
- Keywords: draft, EARS, source-linked

### #40: Activated case (Functional)
While the operating mode is Activated, the cruise control controller shall compute target speed and throttle command according to the active-control requirements.
- Rationale: EARS rewrite of source requirement #40; technical intent requires engineering review before approval.
- Keywords: draft, EARS, source-linked

#### #41: Throttle Value Computation (Functional)
While the operating mode is Activated, the cruise control controller shall compute the throttle command from target speed, vehicle speed, driver throttle input, Kp (20), and Ki (0.199980865671134).
- Rationale: EARS rewrite of source requirement #41; technical intent requires engineering review before approval.
- Keywords: draft, EARS, source-linked

#### #42: Next Target Speed Computation (Functional)
While the operating mode is Activated, when an increment or decrement request is received, the cruise control controller shall compute the next target speed.
- Rationale: EARS rewrite of source requirement #42; technical intent requires engineering review before approval.
- Keywords: draft, EARS, source-linked

### #43: Resume mode (Functional)
While the operating mode is Resume, the cruise control controller shall restore the stored target speed and then compute target speed and throttle command as in Activated mode.
- Rationale: EARS rewrite of source requirement #43; technical intent requires engineering review before approval.
- Keywords: draft, EARS, source-linked

## #44: System Interface (Container)
- Rationale: Structural container retained from source requirement #44.
- Keywords: draft, EARS-structure, source-linked

### #45: Inputs (Container)
- Rationale: Structural container retained from source requirement #45.
- Keywords: draft, EARS-structure, source-linked

#### #46: Enable Switch (Functional)
The cruise control controller shall accept the Enable switch input as a Boolean signal.
- Rationale: EARS rewrite of source requirement #46; technical intent requires engineering review before approval.
- Keywords: draft, EARS, source-linked

#### #47: Cancel Switch (Functional)
The cruise control controller shall accept the Cancel switch input as a Boolean signal.
- Rationale: EARS rewrite of source requirement #47; technical intent requires engineering review before approval.
- Keywords: draft, EARS, source-linked

#### #48: Set Switch (Functional)
The cruise control controller shall accept the Set switch input as a Boolean signal.
- Rationale: EARS rewrite of source requirement #48; technical intent requires engineering review before approval.
- Keywords: draft, EARS, source-linked

#### #49: Resume Switch (Functional)
The cruise control controller shall accept the Resume switch input as a Boolean signal.
- Rationale: EARS rewrite of source requirement #49; technical intent requires engineering review before approval.
- Keywords: draft, EARS, source-linked

#### #50: Increment Switch (Functional)
The cruise control controller shall accept the Increment switch input as a Boolean signal.
- Rationale: EARS rewrite of source requirement #50; technical intent requires engineering review before approval.
- Keywords: draft, EARS, source-linked

#### #51: Decrement Switch (Functional)
The cruise control controller shall accept the Decrement switch input as a Boolean signal.
- Rationale: EARS rewrite of source requirement #51; technical intent requires engineering review before approval.
- Keywords: draft, EARS, source-linked

#### #52: Brake pressure (Functional)
The cruise control controller shall accept brake pressure as an input signal.
- Rationale: EARS rewrite of source requirement #52; technical intent requires engineering review before approval.
- Keywords: draft, EARS, source-linked

#### #53: Vehicle speed (Functional)
The cruise control controller shall accept vehicle speed as an input signal.
- Rationale: EARS rewrite of source requirement #53; technical intent requires engineering review before approval.
- Keywords: draft, EARS, source-linked

#### #54: Key position (Functional)
The cruise control controller shall accept key position as an input signal.
- Rationale: EARS rewrite of source requirement #54; technical intent requires engineering review before approval.
- Keywords: draft, EARS, source-linked

#### #55: Gear position (Functional)
The cruise control controller shall accept gear position as an input signal.
- Rationale: EARS rewrite of source requirement #55; technical intent requires engineering review before approval.
- Keywords: draft, EARS, source-linked

#### #56: Throttle from Driver (Functional)
The cruise control controller shall accept driver throttle position as an input signal.
- Rationale: EARS rewrite of source requirement #56; technical intent requires engineering review before approval.
- Keywords: draft, EARS, source-linked

### #57: Outputs (Container)
- Rationale: Structural container retained from source requirement #57.
- Keywords: draft, EARS-structure, source-linked

#### #58: Driver Request (Functional)
The cruise control controller shall provide reqDrv as a reqMode enumeration.
- Rationale: EARS rewrite of source requirement #58; technical intent requires engineering review before approval.
- Keywords: draft, EARS, source-linked

#### #59: Status (Functional)
The cruise control controller shall provide status as a Boolean signal.
- Rationale: EARS rewrite of source requirement #59; technical intent requires engineering review before approval.
- Keywords: draft, EARS, source-linked

#### #60: Operation Mode (Functional)
The cruise control controller shall provide the operating mode as an opMode enumeration.
- Rationale: EARS rewrite of source requirement #60; technical intent requires engineering review before approval.
- Keywords: draft, EARS, source-linked

#### #61: Target Speed (Functional)
The cruise control controller shall provide target speed as a single-precision signal.
- Rationale: EARS rewrite of source requirement #61; technical intent requires engineering review before approval.
- Keywords: draft, EARS, source-linked

#### #62: Throttle value (Functional)
The cruise control controller shall provide throttle command as a single-precision signal.
- Rationale: EARS rewrite of source requirement #62; technical intent requires engineering review before approval.
- Keywords: draft, EARS, source-linked

### #63: Parameters (Container)
- Rationale: Structural container retained from source requirement #63.
- Keywords: draft, EARS-structure, source-linked

#### #64: Proportional term (Functional)
The cruise control controller shall use Kp (20) as the proportional gain of the PI controller.
- Rationale: EARS rewrite of source requirement #64; technical intent requires engineering review before approval.
- Keywords: draft, EARS, source-linked

#### #65: Integral term (Functional)
The cruise control controller shall use Ki (0.199980865671134) as the integral gain of the PI controller.
- Rationale: EARS rewrite of source requirement #65; technical intent requires engineering review before approval.
- Keywords: draft, EARS, source-linked

#### #66: Threshold value for brake pressure (Functional)
The cruise control controller shall use brake_threshold (5) as the brake-pressure disable threshold.
- Rationale: EARS rewrite of source requirement #66; technical intent requires engineering review before approval.
- Keywords: draft, EARS, source-linked

#### #67: Maximum Throttle Value (Functional)
The cruise control controller shall use throt_max (100) as the maximum throttle command.
- Rationale: EARS rewrite of source requirement #67; technical intent requires engineering review before approval.
- Keywords: draft, EARS, source-linked

#### #68: Minimum Throttle Value (Functional)
The cruise control controller shall use throt_min (0) as the minimum throttle command.
- Rationale: EARS rewrite of source requirement #68; technical intent requires engineering review before approval.
- Keywords: draft, EARS, source-linked

#### #69: Maximum Target Speed (Functional)
The cruise control controller shall use tsp_max (100) as the maximum target speed.
- Rationale: EARS rewrite of source requirement #69; technical intent requires engineering review before approval.
- Keywords: draft, EARS, source-linked

#### #70: Minimum Target Speed (Functional)
The cruise control controller shall use tsp_min (40) as the minimum target speed.
- Rationale: EARS rewrite of source requirement #70; technical intent requires engineering review before approval.
- Keywords: draft, EARS, source-linked
